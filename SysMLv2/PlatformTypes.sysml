package PlatformTypes {
    public import ScalarValues::*;

    comment about PlatformTypes
    /*
     * This package defines platform types and building blocks
     */

    attribute def uint8 :> Positive {}
    attribute def sint16 :> Integer {}
}
